module pydp-external {

  yang-version 1.1;

  namespace "http://example.com/pydp-external";
  prefix pydp-external;

  import ietf-inet-types {
    prefix inet;
  }
  import tailf-common {
    prefix tailf;
  }
  import tailf-ncs {
    prefix ncs;
  }

  description
    "NSO python data provider examples";

  revision 2016-01-01 {
    description
      "Initial revision.";
  }

  container external-data {
    tailf:info "Data outside of NSO";
    list instance {
      tailf:info "An instance of external-data";

      key name;
      leaf name {
	tailf:info "Instance name";
	type string;
      }

      container numbers {
	tailf:info "External number data from http://numbersapi.com";
	config false;
	tailf:callpoint "numbers";
	leaf trivia {
	  tailf:info "Random number trivia from http://numbersapi.com";
	  type string;
	}
	leaf math {
	  tailf:info "Random math facts from http://numbersapi.com";
	  type string;
	}
      }

      container words {
	tailf:info "External word data from https://random-word-api.herokuapp.com";
	config false;
	tailf:callpoint "words";
	leaf random {
	  tailf:info "One random word from https://random-word-api.herokuapp.com";
	  type string;
	}
      }
    }
  }
}
